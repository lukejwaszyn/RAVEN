# RAVEN_Requirements

## #1: System Requirements (Container)

### SYS-FR-001: RAVEN shall autonomously execute a predefined reconnaissance mission along a programmable waypoint path without continuous operator input. (Functional)

### SYS-FR-002: RAVEN shall produce a georeferenced fused data product combining RF spectrum data and LIDAR terrain mapping as the primary mission output. (Functional)

### SYS-FR-003: RAVEN shall operate as a two-segment system consisting of a Ground Control Segment and an Aerial Vehicle Segment communicating over a defined data link. (Functional)

### SYS-PR-001: RAVEN shall sustain autonomous flight for a minimum of 10 minutes under nominal operating conditions, with an objective of 20 minutes. (Functional)

### SYS-PR-002: RAVEN shall maintain end-to-end command and telemetry latency not exceeding 500ms under nominal link conditions. (Functional)

### SYS-IR-001: RAVEN shall provide a single-operator ground control interface capable of commanding, monitoring, and terminating a mission from one workstation. (Functional)

## #8: GCS Mission Control (Container)

### GCS-MC-FR-001: The Mission Control subsystem shall provide a mission planning interface enabling the operator to define, modify, and upload waypoint paths to the AVS prior to flight. (Functional)

### GCS-MC-FR-002: The Mission Control subsystem shall execute autonomous mission logic including waypoint sequencing, loiter commands, and return-to-launch without continuous operator input. (Functional)

### GCS-MC-FR-003: The Mission Control subsystem shall monitor AVS system state and alert the operator to any off-nominal condition during flight. (Functional)

### GCS-MC-FR-004: The Mission Control subsystem shall provide a mission abort command that triggers immediate return-to-launch on the AVS. (Functional)

### GCS-MC-PR-001: The Mission Control subsystem shall display real-time AVS position, altitude, heading, and battery state at a minimum refresh rate of 2 Hz. (Functional)

### GCS-MC-IR-001: The Mission Control subsystem shall interface with the Flight Telemetry subsystem via MAVLink protocol to send commands and receive AVS state data. (Functional)

## #15: GCS Flight Telemetry (Container)

### GCS-FT-FR-001: The Flight Telemetry subsystem shall maintain a bidirectional data link with the AVS for the duration of each mission. (Functional)

### GCS-FT-FR-002: The Flight Telemetry subsystem shall detect and annunciate data link loss to the Mission Control subsystem within 1 second of link failure. (Functional)

### GCS-FT-PR-001: The Flight Telemetry subsystem shall sustain command and telemetry throughput sufficient to support MAVLink message rates at no less than 4 Hz. (Functional)

### GCS-FT-IR-001: The Flight Telemetry subsystem shall support WiFi as the primary link and shall be configurable to operate over RFD900x radio as a contingency link. (Functional)

## #20: GCS Data Processing (Container)

### GCS-DP-FR-001: The Data Processing subsystem shall ingest RTL-SDR IQ data streamed from the AVS and produce georeferenced RF spectrum snapshots tagged with position and timestamp. (Functional)

### GCS-DP-FR-002: The Data Processing subsystem shall ingest LIDAR point cloud data from the AVS and produce a georeferenced terrain map. (Functional)

### GCS-DP-FR-003: The Data Processing subsystem shall fuse georeferenced RF data and LIDAR terrain data into a single overlaid data product. (Functional)

### GCS-DP-FR-004: The Data Processing subsystem shall display live RF spectrum data received from the AVS during flight. (Functional)

### GCS-DP-PR-001: The Data Processing subsystem shall georeference all RF and LIDAR data to within a positional accuracy consistent with the onboard GPS solution. (Functional)

### GCS-DP-IR-001: The Data Processing subsystem shall receive IQ data via rtl_tcp stream from the AVS Flight Computer over the active data link. (Functional)

### GCS-DP-IR-002: The Data Processing subsystem shall receive LIDAR point cloud logs from the AVS Flight Computer via post-flight file transfer or live stream over the data link. (Functional)

## #28: AVS Structures (Container)

### AVS-ST-FR-001: The Structures subsystem shall provide a rigid airframe capable of supporting all AVS subsystems including flight controller, flight computer, RF payload, and LIDAR payload during flight. (Functional)

### AVS-ST-FR-002: The Structures subsystem shall provide dedicated mounting points for the LIDAR sensor with unobstructed downward field of view. (Functional)

### AVS-ST-FR-003: The Structures subsystem shall provide dedicated mounting for the RTL-SDR and antenna with RF line-of-sight clearance from the airframe. (Functional)

### AVS-ST-IR-001: The Structures subsystem shall conform to the F450 quadcopter frame form factor as the baseline airframe platform. (Functional)

## #33: AVS Propulsion (Container)

### AVS-PR-FR-001: The Propulsion subsystem shall provide sufficient thrust to lift the fully loaded AVS including all payload and power systems. (Functional)

### AVS-PR-FR-002: The Propulsion subsystem shall accept motor commands from the Flight Control subsystem via the flight controller ESC interface. (Functional)

### AVS-PR-PR-001: The Propulsion subsystem shall provide a thrust-to-weight ratio of not less than 2:1 at hover under full payload configuration. (Functional)

### AVS-PR-PR-002: The Propulsion subsystem shall sustain nominal flight operations for the duration of SYS-PR-001 minimum flight time on a single battery charge. (Functional)

### AVS-PR-IR-001: The Propulsion subsystem shall accept 4S LiPo power input from the Power subsystem via the power distribution board. (Functional)

## #39: AVS Flight Control (Container)

### AVS-FC-FR-001: The Flight Control subsystem shall execute autonomous waypoint navigation using ArduPilot firmware. (Functional)

### AVS-FC-FR-002: The Flight Control subsystem shall execute a return-to-launch command upon receipt of an abort command from the GCS or upon data link loss exceeding the defined failsafe threshold. (Functional)

### AVS-FC-FR-003: The Flight Control subsystem shall perform attitude stabilization, altitude hold, and position hold using onboard IMU, barometer, and GPS inputs. (Functional)

### AVS-FC-FR-004: The Flight Control subsystem shall accept mission waypoint uploads from the GCS via MAVLink. (Functional)

### AVS-FC-PR-001: The Flight Control subsystem shall maintain position hold within 2 meters of commanded position under nominal wind conditions. (Functional)

### AVS-FC-IR-001: The Flight Control subsystem shall interface with the Flight Computer subsystem via MAVLink over serial UART. (Functional)

### AVS-FC-IR-002: The Flight Control subsystem shall interface with the Propulsion subsystem via PWM or DSHOT ESC protocol. (Functional)

## #47: AVS Flight Computer (Container)

### AVS-CP-FR-001: The Flight Computer subsystem shall operate as a headless companion computer executing the UAV daemon software. (Functional)

### AVS-CP-FR-002: The Flight Computer subsystem shall bridge MAVLink telemetry between the Flight Control subsystem and the GCS. (Functional)

### AVS-CP-FR-003: The Flight Computer subsystem shall serve RTL-SDR IQ data to the GCS via rtl_tcp over the active data link. (Functional)

### AVS-CP-FR-004: The Flight Computer subsystem shall log LIDAR point cloud data with timestamps for post-flight processing. (Functional)

### AVS-CP-FR-005: The Flight Computer subsystem shall tag all sensor data with GPS coordinates via GPSd. (Functional)

### AVS-CP-FR-006: The Flight Computer subsystem shall implement graceful fault handling for data link loss and sensor dropout without interrupting flight operations. (Functional)

### AVS-CP-IR-001: The Flight Computer subsystem shall be implemented on a Raspberry Pi 5 4GB as the baseline hardware platform. (Functional)

### AVS-CP-IR-002: The Flight Computer subsystem shall receive power from the Power subsystem via 5V BEC from the UAV battery bus during flight. (Functional)

## #56: AVS RF SDR (Container)

### AVS-RF-FR-001: The RF subsystem shall capture IQ samples across a configurable frequency range during flight. (Functional)

### AVS-RF-FR-002: The RF subsystem shall stream captured IQ data to the Flight Computer via USB for forwarding to the GCS. (Functional)

### AVS-RF-PR-001: The RF subsystem shall support a minimum instantaneous receive bandwidth of 2.4 MHz. (Functional)

### AVS-RF-PR-002: The RF subsystem shall operate across a tunable frequency range of 500 kHz to 1.766 GHz. (Functional)

### AVS-RF-IR-001: The RF subsystem shall be implemented using the RTL-SDR Blog V4 as the baseline SDR hardware. (Functional)

### AVS-RF-IR-002: The RF subsystem shall connect to the Flight Computer via USB interface. (Functional)

## #63: AVS LIDAR (Container)

### AVS-LI-FR-001: The LIDAR subsystem shall continuously capture 2D point cloud scans of terrain below the AVS during flight. (Functional)

### AVS-LI-FR-002: The LIDAR subsystem shall log all point cloud data with timestamps to the Flight Computer for georeferencing. (Functional)

### AVS-LI-PR-001: The LIDAR subsystem shall achieve a minimum scan range of 6 meters under nominal operating conditions. (Functional)

### AVS-LI-PR-002: The LIDAR subsystem shall operate at a minimum scan frequency of 5.5 Hz. (Functional)

### AVS-LI-IR-001: The LIDAR subsystem shall be implemented using the RPLidar A1M8 as the baseline sensor. (Functional)

### AVS-LI-IR-002: The LIDAR subsystem shall interface with the Flight Computer via USB. (Functional)

## #70: AVS Power (Container)

### AVS-PW-FR-001: The Power subsystem shall provide primary flight power to all AVS subsystems from a single LiPo battery. (Functional)

### AVS-PW-FR-002: The Power subsystem shall provide regulated 5V DC power to the Flight Computer via BEC during flight. (Functional)

### AVS-PW-PR-001: The Power subsystem shall provide sufficient capacity to satisfy SYS-PR-001 minimum flight duration under full payload load. (Functional)

### AVS-PW-IR-001: The Power subsystem shall be implemented using a 4S 3300mAh LiPo as the baseline power source. (Functional)

## #75: Data Link (Container)

### DL-FR-001: The Data Link shall provide a bidirectional communication channel between the GCS and AVS supporting MAVLink telemetry, IQ data streaming, and LIDAR data transfer. (Functional)

### DL-FR-002: The Data Link shall support WiFi as the primary link architecture. (Functional)

### DL-FR-003: The Data Link shall support RFD900x radio as a configurable contingency link for MAVLink telemetry in environments where WiFi is unavailable or unreliable. (Functional)

### DL-FR-004: The Data Link shall maintain continuous MAVLink telemetry for the duration of each mission. (Functional)

### DL-PR-001: The Data Link shall sustain end-to-end command and telemetry latency not exceeding 500ms under nominal link conditions per SYS-PR-002. (Functional)

### DL-PR-002: The Data Link shall support simultaneous MAVLink telemetry and IQ data streaming without throughput degradation to either channel. (Functional)

### DL-IR-001: The Data Link shall interface with the GCS Flight Telemetry subsystem on the ground segment side. (Functional)

### DL-IR-002: The Data Link shall interface with the AVS Flight Computer subsystem on the aerial vehicle side. (Functional)
